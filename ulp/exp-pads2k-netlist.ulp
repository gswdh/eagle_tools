#usage "Export Netlist in PADS2K format."
       "Resulting file is saved in the same location as sch/board pair."
       
/*
*******************************************************************************
* Jorge Garcia, Cadsoft Computer
* February 24, 2015
* 
* Copyright (c) 2015 Newark, Premier Farnell DBA Cadsoft Computer
* 
* Permission is hereby granted, free of charge, to any person obtaining a copy 
* of this software and associated documentation files (the "Software"), to deal 
* in the Software without restriction, including without limitation the rights 
* to use, copy, modify, merge, publish, distribute, sublicense, and/or sell 
* copies of the Software, and to permit persons to whom the Software is 
* furnished to do so, subject to the following conditions:
* 
* The above copyright notice and this permission notice shall be included in 
* all copies or substantial portions of the Software.
* 
* THE SOFTWARE IS PROVIDED "AS IS", WITHOUT WARRANTY OF ANY KIND, EXPRESS OR 
* IMPLIED, INCLUDING BUT NOT LIMITED TO THE WARRANTIES OF MERCHANTABILITY, 
* FITNESS FOR A PARTICULAR PURPOSE AND NONINFRINGEMENT. IN NO EVENT SHALL THE 
* AUTHORS OR COPYRIGHT HOLDERS BE LIABLE FOR ANY CLAIM, DAMAGES OR OTHER 
* LIABILITY, WHETHER IN AN ACTION OF CONTRACT, TORT OR OTHERWISE, ARISING 
* FROM, OUT OF OR IN CONNECTION WITH THE SOFTWARE OR THE USE OR OTHER DEALINGS 
* IN THE SOFTWARE.
*******************************************************************************
*/
                                                                                
/*
*******************************************************************************
*                               REVISION HISTORY                              *
*                                                                             *
* 2/24/2015     Initial Release V1.0                                          *
*******************************************************************************
*/ 

/*
*******************************************************************************
*                               NON-GUI FUNCTIONS                             *
*******************************************************************************
*/

/*
*******************************************************************************
*                             Gather_Components()
* Description:      This function returns string with all of the part reference
*                   designators and package names.
* 
* Argument(s):      None
* 
* Return(s):        string with all of the info
* 
* Caller(s):        Create_File()
* 
* Notes:            none
*******************************************************************************
*/

string Gather_Components () {
    string data;
    string elem;
    
    board(B) {
        B.elements(E) {
            sprintf(elem,"%-17s%s\n",E.name,E.package.name);
            data += elem;
        }
    }
    
    return data;
}

/*
*******************************************************************************
*                             Gather_Signals()
* Description:      This function returns a string with all of the signals
*                   definining what points they connect to. Each line contains
*                   a maximum of 8 connection points.
* 
* Argument(s):      None
* 
* Return(s):        string with all of the necessary information
* 
* Caller(s):        Create_File
* 
* Notes:            none
*******************************************************************************
*/

string Gather_Signals () {
    string data;
    string elem;
    string array[];
    int index = 0;
    int i = 0;
    
    board(B) {
        B.signals(S) {
            sprintf(elem,"*SIGNAL* %s\n", S.name);
            data += elem;
            S.contactrefs(C) {
                sprintf(elem, "%s.%s", C.element.name, C.contact.name);
                array[index] = elem;
                index++;
            }
            for (i = 0; i < index; i++) {
                if (i == index-1) {
                    data += array[i]+"\n";
                }
                else if ((i-7)%8 == 0) {                                        /* The idea here is that a new row is...*/
                    data += array[i]+"\n";                                      /* ...formed every 8 entries.           */
                }
                else {
                    data += array[i]+" ";
                }
            }
            index = 0;
        }
    }
    
    return data;
}

/*
*******************************************************************************
*                                   MAIN()                                    *
*******************************************************************************
*/

int main() {
    string parts;
    string nets;
    string path;
   
    if (board) {
        board(B) {
            path = dlgFileSave("Save PADS2K Netlist", filesetext(B.name, ".asc"), "*.asc");
            if (path == "") {
                exit(0);
            }
            output(path,"wt") {
                printf("*PADS-PCB*\n");
                printf("*PART*\n");
                parts = Gather_Components();
                printf("%s", parts);
                printf("\n");
                printf("*NET*\n");
                nets = Gather_Signals();
                printf("%s", nets);
                printf("*END*");
            }
        }       
    }
    else {
        dlgMessageBox("!Start this ULP in a Board.");
        exit (0);
    }
    return 0;
}
