#usage "<b>Exports a netlist from Eagle to Allegro.</b>\n"
"v1.0 2009/07/27\n"
"<p>"
"This ULP exports parts and nets from Eagle schematic into a Telesis netlist that can be imported from Cadence Allegro (File/Import/Logic/Other), "
"and create associated device files for all parts.\n"
"See Allegro PCB Editor User Guide / Transferring Logic Design Data / Transfering 3rd party logic for more info about import process.\n"
"Tested with OrCAD v16.2.\n"
"<p>"
"<author>Author: Eric HEURTEL eric(at)sound4.biz"

string fileName, devFileName;
string dirName;
string devName;
string packName;
string value;
string logText;
int t = time();

// ----------
// Look for any of the substrings (given in subs separated by space) in string s.
// Returns substring index in s or -1 if not found
// ----------
int look4substring( string subs, string s )
{
   string sublist[] ;
   int nbSub;
   int index = -1 ;
   
   nbSub = strsplit( sublist, subs, ' ' ) ;
   while ( ( nbSub > 0) && (index == -1 ) )
   {
      index = strstr( s, sublist[--nbSub] ) ;
   }
   return index ;
}


// ----------
// Replaces tok characters from string s into rep characters
// ----------
string RESERVED_CHARS  = "&~#'{([|`@)]}=+$%*!§:/;,.? " ;
string REPLACING_CHARS = "___________________________" ;  // Must have same length as RESERVED_CHARS
string strtok( string s, string tok, string rep)
{
   for ( int i = 0; i < strlen(s); i++ )
   {
      for ( int j = 0; j < strlen(tok); j++ )
      {
         s[i] = (s[i] == tok[j]) ? rep[j] : s[i] ;
      }
   }
   return s ;
}


// ----------
// Removes non printable chars
// ----------
string strclean( string s)
{
   for (int i = 0; s[i]; ++i)
   {
      s[i] = (s[i] <= 32) ? ' ' : s[i] ;
   }
   return s ;
}


// ----------
// Wrap given string into lines of 60 chars max 
// (OrCAD doc defines a limit to 78 chars; in practice it is 1024 chars)
// ----------
string WrapLine( string s )
{
   string text = "";
   string line = "";
   string word = "";
   int linelen = 0 ;
   
   for ( int i = 0; i < strlen(s); i++ )
   {
      word += s[i] ;
      linelen += 1 ;
      if ( s[i] == ' ' )
      {
         // end of word
         if ( linelen >= 60 )
         {
            // last word exceeds line : word written on next line
            text += line + ",\n   ";
            line = "" ;
            linelen = 3 ;
         }
         line += word ;
         word = "" ;
      }
   }
   text += line + word;    // FIXME (if necessary) : Last line may exceed 80 chars here...
   return text ;
}


// ----------
// main
// ----------
if (! schematic)
{
   dlgMessageBox("\n    Start this ULP in a schematic !    \n");
   exit(0);
}
dirName = dlgDirectory("Select the output directory", ""); 
if (dirName != "") schematic(SCH)
{
   // ---------------------------------------
   // Parsing parts and Creating Netlist
   // ---------------------------------------
   fileName = dirName + filename(filesetext(SCH.name, ".net")) ;
   logText += "Creating " + fileName + " netlist file.\n" ;
   output(fileName) 
   {
      printf( "(Netlist exported from Eagle %s schematic to Telesis/Allegro netlist)\n", filename(SCH.name));
      printf( "(Date %d-%d-%d %d:%d:%d)\n", t2year(t), t2month(t), t2day(t), t2hour(t), t2minute(t), t2second(t) );
      printf( "(PACKAGE format is :)\n");
      printf( "([packagename] !devicetype [!value[!tolerance]];reference_designator...)\n");
      printf( "(Package names and Value defined here overwrite package name and Value defined in the Device File.)\n");
      printf( "(See Allegro PCB Editor User Guide / Transferring Logic Design Data / Creating, Comparing, and Updating Databases for more info.)\n" );
      
      // Parsing parts and listing packages records
      logText += "Parsing parts and listing device files...\n" ;
      printf( "$PACKAGES\n" ) ;
      
      SCH.parts(P)
      {
         // Leave parts that are not chip (frames, supplies)
         if (P.device.package)
         {
            value = strtok( P.value, "µ%/.#, ()", "u________" );
            devName = strtok( P.device.name, RESERVED_CHARS, REPLACING_CHARS ) + "-" + value ;
            packName = P.device.package.name ;
            printf("%s! %s! '%s'; %s\n", strtok( packName, RESERVED_CHARS, REPLACING_CHARS ), devName, value, P.name ) ;
         }
      }  // SCH.parts(P)


      // Parsing nets and listing net records
      logText += "Parsing parts and listing net records...\n" ;
      printf( "\n" ) ;
      printf( "(NETS format is :)\n");
      printf( "([netname] ; reference_designator.pin_number)\n");
      printf( "(See Allegro PCB Editor User Guide / Transferring Logic Design Data / Creating, Comparing, and Updating Databases for more info.)\n" );
      
      printf( "$NETS\n" ) ;
      SCH.nets(N)
      {
         string netPins = "" ;
         string pinName;
         
         printf( "'%s' ; ", N.name);
         N.pinrefs(PR) 
         {
            // Rename special pin names here...
            if ( PR.pin.contact.name == "K" )
               pinName = "1";
            else if ( PR.pin.contact.name == "A" )
               pinName = "2";
            else 
               pinName = strtok( PR.pin.contact.name, "$+-,.", "_12__" ) ;

            netPins += PR.part.name + "."  + pinName + " ";
         }
            printf( WrapLine( netPins ) );
         printf("\n");
      }
      
      printf( "$END\n" ) ;
   }  // output(fileName) 

   // ---------------------------------------
   // Parsing parts again and creating device files
   // ---------------------------------------
   logText += "Parsing parts and creating device files...\n" ;
   
   SCH.parts(P)
   {
      // Leave parts that are not chip (frames, supplies)
      if (P.device.package)
      {
         value = strtok( P.value, "µ%/.#, ()", "u________" );
         devName = strtok( P.device.name, RESERVED_CHARS, REPLACING_CHARS ) + "-" + value ;
         packName = P.device.package.name ;
         packName = strtok( packName, RESERVED_CHARS, REPLACING_CHARS ) ;
         devFileName = dirName + devName + ".txt" ;
         logText += "Creating " + devFileName + " device file (from Eagle " + P.device.name + " device / " + P.device.library + " library).\n" ;
         
         output(devFileName)
         {
            printf( "(Orcad device %s)\n", devName);
            printf( "(Eagle device : %s)\n", P.device.name);
            printf( "(Eagle library : %s)\n", P.device.library);
            printf( "(Eagle Description : %s)\n", strclean(P.device.description) );
            printf( "(Exported from Eagle %s schematic to Telesis/Allegro netlist)\n", filename(SCH.name));
            printf( "(Date %d-%d-%d %d:%d:%d)\n", t2year(t), t2month(t), t2day(t), t2hour(t), t2minute(t), t2second(t) );
            printf( "(One device file is required for each device type; Device files contain physical information for the components in the netlist.)\n");
            printf( "(Package names and Value defined here are overwritten by package name and Value defined in the Netlist.)\n");
            printf( "(See Allegro PCB Editor User Guide / Defining and Developing Libraries / Preparing Device Files for more info.)\n" );
            printf( "PACKAGE %s\n", packName ) ;
            
            string devClass = P.device.prefix;
            switch ( toupper( devClass[0] ) ) 
            {
               case 'I' :
               case 'U' : devClass = "IC" ; break ;
               case 'J' :
               case 'X' : devClass = "IO" ; break ;
               default : devClass = "DISCRETE" ;
            }
            printf("CLASS %s\n", devClass ) ;
            
            // Parse each device and each gate
            string gateName[];
            string symbName[];
            string pinName[];
            string pinNbr[];
            string pinType[];
            string swapList[];
            int pinCnt = 0 ;
            int gateCnt = 0 ;
            int i ;
            string pName ;
            
            P.device.gates(G) 
            {
               string pinSwap[];
               int    swapLvl[];
               int swapCnt = 0 ;

               gateName[gateCnt] = strsub( strtok( G.name, RESERVED_CHARS, REPLACING_CHARS ), 0, 30) ;
               symbName[gateCnt] = strsub( strtok( G.symbol.name, RESERVED_CHARS, REPLACING_CHARS ), 0, 30) ;
               pinName[gateCnt] = "";
               pinNbr[gateCnt] = "";
               pinType[gateCnt] = "";
               swapList[gateCnt] = "" ;

               // Parse each gate pin
               G.symbol.pins(S) 
               {
                  pinCnt++;
                  pName = "'" + strsub( strtok( S.name, "!/", "__"), 0, 30) + "'" ;
                  pinName[gateCnt] += pName + " " ;
                  if ( S.contact.name == "K" )
                     pinNbr[gateCnt] += "1 ";
                  else if ( S.contact.name == "A" )
                     pinNbr[gateCnt] += "2 ";
                  else 
                     pinNbr[gateCnt] += strtok(S.contact.name, "$+-,.", "_12__" ) + " " ;
                  switch ( S.direction ) 
                  {
                     case PIN_DIRECTION_IN :  pinType[gateCnt] += "IN " ; break ;
                     case PIN_DIRECTION_OUT : pinType[gateCnt] += "OUT " ; break ;
                     case PIN_DIRECTION_IO :  pinType[gateCnt] += "BI " ; break ;
                     case PIN_DIRECTION_OC :  pinType[gateCnt] += "OCL " ; break ;
                     case PIN_DIRECTION_HIZ : pinType[gateCnt] += "TRI " ; break ;
                     case PIN_DIRECTION_NC :  pinType[gateCnt] += "NC " ; break ;
                     case PIN_DIRECTION_SUP : 
                     case PIN_DIRECTION_PWR : 
                        if      ( look4substring( "VCC VDD VANA +", S.name ) >= 0 ) { pinType[gateCnt] += "POWER " ; }
                        else if ( look4substring( "GND VSS", S.name ) >= 0 ) { pinType[gateCnt] += "GROUND " ; }
                        else { pinType[gateCnt] += "UNSPEC " ; }
                        break ;
                     case PIN_DIRECTION_PAS : 
                     default :                pinType[gateCnt] += "UNSPEC ";
                  }
                  if ( S.swaplevel > 0 )
                  {
                     for ( i = 0; (i < swapCnt) && (S.swaplevel != swapLvl[i]); i++ );
                     if ( i == swapCnt )
                     {
                        swapLvl[i] = S.swaplevel ;
                        pinSwap[i] = "" ;
                        swapCnt++ ;
                     }
                     pinSwap[i] += pName + " " ;
                  }
               }

               // Generate swap list for the gate
               for ( i = 0; i < swapCnt; i++ )
               {
                  swapList[gateCnt] += "PINSWAP " + symbName[gateCnt] + " " + WrapLine( pinSwap[i] ) + "\n" ;
               }
               gateCnt++ ;
            }
            
            printf("PINCOUNT %d\n", pinCnt ) ;
            for ( i = 0; i < gateCnt; i++ )
            {
               for ( int j = 0; (j < i) && (symbName[i] != symbName[j]); j++ ) ;
               if ( i == j )
               {
                  printf( "PINORDER %s %s\n", symbName[i], WrapLine( pinName[i] ) );
                  printf( "PINUSE %s %s\n",   symbName[i], WrapLine( pinType[i] ) );
                  printf( swapList[i] ) ;
               }
               printf("FUNCTION %s %s %s\n", gateName[i], symbName[i], WrapLine( pinNbr[i] ) );
            }
            
            printf("PACKAGEPROP PART_NAME %s\n", P.device.prefix );
            // default VALUE not necessary because netlist defines it for every part.
            printf("PACKAGEPROP VALUE %s\n", value );
            printf("END\n");
            printf("\n");
         }  // output(devFileName)
      }  // if (P.device.package)
   }  // SCH.parts(P)
   
   logText += "End.\n" ;

   fileName = dirName + filename(filesetext(SCH.name, ".log")) ;
   output(fileName)
   {
      printf( "%s", logText ) ;
   }

   dlgMessageBox ("Telesis/Allegro Netlist exported.\nLog written to " + fileName + " file." );
} // if (schematic)
