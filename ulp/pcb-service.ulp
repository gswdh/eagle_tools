#usage "en: <b>PCB Quote Service</b\n>"
           "<p>"
           "Get a quote for manufacturing your PCB.<br>",
       "de: <b>PCB-Angebots-Service</b>\n"
           "<p>"
           "Hiermit gelangen Sie zu einem Angebot zur Fertigung Ihres Boards.<p>"
           "<author>Autor: support@cadsoft.de</author><p>"
// THIS PROGRAM IS PROVIDED AS IS AND WITHOUT WARRANTY OF ANY KIND, EXPRESSED OR IMPLIED

#require 5.1000
string Version = "10";

// Debug stuff
int    Debug = 0;
string DbgFile;
string DbgMsg;

// Available (service) targets
enum { Element14, EuroCircuits };
int Target;

// Country settings
string CountryData[] = {
      "AT", "Austria",             "1",
      "BE", "Belgium",             "1",
      "BR", "Brasil",              "0",
      "BG", "Bulgaria",            "1",
      "CA", "Canada",              "0",
      "HR", "Croatia",             "1",
      "CY", "Cyprus",              "1",
      "CZ", "Czech Republic",      "1",
      "DK", "Denmark",             "1",
      "EE", "Estonia",             "1",
      "FI", "Finland",             "1",
      "FR", "France",              "1",
      "DE", "Germany",             "1",
      "GR", "Greece",              "1",
      "HU", "Hungary",             "1",
      "IS", "Iceland",             "1",
      "IE", "Ireland",             "1",
      "IT", "Italy",               "1",
      "LV", "Latvia",              "1",
      "LI", "Liechtenstein",       "1",
      "LT", "Lithuania",           "1",
      "LU", "Luxembourg",          "1",
      "MK", "Macedonia",           "1",
      "MT", "Malta",               "1",
      "MX", "Mexico",              "0",
      "MC", "Monaco",              "1",
      "ME", "Montenegro",          "1",
      "NL", "Netherlands",         "1",
      "NO", "Norway",              "1",
      "PL", "Poland",              "1",
      "PT", "Portugal",            "1",
      "RO", "Romania",             "1",
      "SM", "San Marino",          "1",
      "RS", "Serbia",              "1",
      "SK", "Slovakia",            "1",
      "SI", "Slovenia",            "1",
      "ES", "Spain",               "1",
      "SE", "Sweden",              "1",
      "CH", "Switzerland",         "1",
      "TR", "Turkey",              "1",
      "GB", "United Kingdom",      "1",
      "US", "USA",                 "0",
      "??", "Other country",       "0"
   };
int CountryRecSize = 3;
string Countries[];
int CountryIdx = -1;

string Warnings;
int Useless;  // When a quote doesn't make sense (e.g empty board or such)

// Design rules
int Export = 1;
string DruFile;

// Handling change of internal units V5 -> V6:
int UFactor = (EAGLE_VERSION < 6 && EAGLE_RELEASE < 12) ? 1 : 32;

// Quote Parameters
string BoardName;
int NrUsedLayers;
int CopperThicknessOutside = INT_MAX;
int CopperThicknessInside = INT_MAX;
int MaterialThickness;
int MinTraceWidth = INT_MAX;
int MinHoleSize = INT_MAX;
string SolderSides;
string SilkScreenSides;
int NrBlindBuriedTypes;
int MinPitch = INT_MAX;
int NrSmdPadsTop;
int NrSmdPadsBottom;
// For computing width and height
real XMin = REAL_MAX, XMax = -REAL_MAX, YMin = REAL_MAX, YMax = -REAL_MAX;

// Language support for dialogs: German/English
// Please keep to alphabetic sorting for better maintainability !
string Dictionary[] = {
  "en\v"
  "de\v",
  "Board length (dimension Y):\v"
  "Boardlänge  (Y-Richtung):\v",
  "Board name:\v"
  "Boardname:\v",
  "Board thickness:\v"
  "Boarddicke:\v",
  "Board width  (dimension X):\v"
  "Boardbreite (X-Richtung):\v",
  "Board width and length could not be determined from dimension layer. \v"
  "Boardbreite und -länge konnten nicht bestimmt werden anhand des Dimension-Layers. \v",
  "Both Sides\v"
  "beidseitig\v",
  "Bottom Side\v"
  "unten\v",
  "Please use the dimension layer to design the board outline.\v"
  "Bitte benutzen Sie den Dimension-Layer, um die Boardumrisse festzulegen.\v",
  "Calculating quote parameters...\v"
  "Berechne Angebots-Parameter...\v",
  "Change Country:\v"
  "Land wechseln:\v",
  "Close\v"
  "Schliessen\v",
  "+Continue...\v"
  "+Weiter...\v",
  "Copper thickness outer layers:\v"
  "Kupferstärke aussen:\v",
  "Copper thickness inner layers:\v"
  "Kupferstärke innen:\v",
  "Estimate based on outer layers failed. \v"
  "Schätzung basierend auf Aussen-Layer fehlgeschlagen. \v",
  "Estimation based on outer layers. \v"
  "Schätzung basierend auf Aussen-Layer. \v",
  "Get PCB Quote\v"
  "Zum PCB-Angebot\v",
  "A quote for this board doesn't make sense yet !\v"
  "Ein Angebot für dieses Board macht noch keinen Sinn !\v",
  "If you want to get a quote anyway, please follow the link.\v"
  "Wenn Sie dennoch ein Angebot erhalten wollen, folgen Sie bitte dem Link.\v",
  "Information:\v"
  "Hinweise:\v",
  "Minimum hole size:\v"
  "Kleinster Bohrdurchmesser:\v",
  "Minimum SMD pitch:\v"
  "Kleinster SMD-Abstand:\v",
  "Minimum trace width (track width):\v"
  "Kleinste Bahnbreite:\v",
  "Minimum trace width could not be determined.\v"
  "Minimale Bahnbreite konnte nicht bestimmt werden.\v",
  "No copper found in the signal layers. \v"
  "Kein Kupfer in den Signal-Layern vorhanden. \v",
  "None\v"
  "keine\v",
  "Number of blind or buried hole types:\v"
  "Anzahl von Blind- oder Buried-Bohrungsarten:\v",
  "Number of SMD pads on bottom:\v"
  "Anzahl von SMD-Pads unten:\v",
  "Number of SMD pads on top:\v"
  "Anzahl von SMD-Pads oben:\v",
  "Number of layers:\v"
  "Anzahl Layer:\v",
  "Wire(s) and/or polygon(s) with zero width found on signal layer(s). \v"
  "Bahnen und/oder Polygone mit Breite 0 in Signal-Layer(n) gefunden. \v",
  "None of the signal layers are used. Number of layers could not be determined.\v"
  "Keines der Signal-Layer wird verwendet. Layeranzahl konnte nicht bestimmt werden.\v",
  "Parameters:\v"
  "Parameter:\v",
  "PCB Quote Service\v"
  "PCB-Angebots-Service\v",
  "Please start from Layout editor !\v"
  "Bitte starten Sie vom Layout-Editor aus !\v",
  "Silkscreen sides:\v"
  "Bestückungsdruck-Seiten:\v",
  "Solder sides:\v"
  "Lötseiten:\v",
  "There are still airwires left.\v"
  "Es sind noch Luftlinien vorhanden.\v",
  "Top Side\v"
  "oben\v",
  "undefined\v"
  "unbestimmt\v",
  "Warnings:\v"
  "Warnungen:\v",
  "Your board layout is incomplete:\v"
  "Ihr Board-Layout ist unvollständig:\v"
};

string DlgLang = language();
if (DlgLang != "de") DlgLang = "en";
int LangIdx = strstr(Dictionary[0], DlgLang) / 3;

// Translate, based on dictionary
string tr(string s) {
  string t = lookup(Dictionary, s, LangIdx, '\v');
  return t ? t : s;
}

string Unknown = tr("undefined");

//- Auxiliary functions -------------------------------------------------------

void InitCountry() {
   int i;
   // Initial run: Country (index) not determined yet.
   if (CountryIdx == -1)
      for ( ; CountryData[i] != ""; i += CountryRecSize) {
         Countries[i / CountryRecSize] = CountryData[i + 1];
         if (CountryData[i] == country()) CountryIdx = i / CountryRecSize;
      }
   // Country not found: Set it to "Other country" (must be the last one!)
   if (CountryIdx == -1) CountryIdx = i / CountryRecSize - 1;
   // Set target accordingly
   Target = strtol(CountryData[CountryRecSize * CountryIdx + 2]);
}

void NotifyE14() {
   string postStr =
      "<?xml version=\"1.0\" encoding=\"UTF-8\"?>"
      "<pfXML xmlns:xsi=\"http://www.w3.org/2001/XMLSchema-instance\">"
      "   <Header>"
      "      <PartnerID>SBP003</PartnerID>"
      "      <TransactionID>459156168464156</TransactionID>"
      "      <Timestamp>" + t2string(time(), "Uyyyy-MM-ddThh:mm:ss.000") + "</Timestamp>"
      "      <MessageType>Referral</MessageType>"
      "      <ReferrerID>CadSoft</ReferrerID>"
      "      <Locale>" + country() + "</Locale>"
      "   </Header>"
      "</pfXML>";
   string answer;
   int rv = netpost(answer, "https://b2b.premierfarnell.com/BtsHttpReceive/BTSHTTPReceive.dll?SBPDocGeneric", postStr);
   if (Debug && rv < 0) {
      sprintf(DbgMsg, "Oops ! Post on E14 failed ! Error code: %d\n Net error message: " + neterror(), rv);
      dlgMessageBox(DbgMsg);
   }
}

string GetTargetURL() {
   return (Target == Element14) ? "http://www.element-14.com/community/pcb-services-pentalogix!usquickturn.jspa" :
                                  "http://be.eurocircuits.com/basic/element14/cadsoft.aspx";
}

string I2Str(int i) {
   string str;
   sprintf(str, "%d", i);
   return str;
}

// HTML stuff
string LItem(string txt) {
   return  "<li>" + txt +  "</li>";
}

string Bold(string txt) {
   return  "<b>" + txt + "</b>";
}

// Unit handling
string U2EUStr(int i) {
   string str;
   sprintf(str, "%f", (Target == Element14) ? u2inch(i) : u2mm(i));
   return str;
}

string U2EUStrN(int i) {
   return U2EUStr(i) + " " + (Target == Element14 ? "in" : "mm");
}

string U2CoppThickEUStr(int i) {  // The US like to have ounces, the rest of the world mm ...
   string str;
   sprintf(str, "%f", (Target == Element14) ? i/(350.0 * UFactor) : u2mm(i));
   return str;
}

string U2CoppThickEUStrN(int i) {
   return U2CoppThickEUStr(i) + (Target == Element14 ? " oz" : " mm");
}

int Str2U(string s) {
   if (strstr(s, "mm") > 0) return int(strtod(s) * 10000 * UFactor);
   if (strstr(s, "mil") > 0) return int(strtod(s) * 10 * UFactor * 25.4);
   if (strstr(s, "in") > 0) return int(strtod(s) * 10000 * UFactor * 25.4);
   if (strstr(s, "mic") > 0) return int(strtod(s) * 10 * UFactor);
   dlgMessageBox("Unknown unit in design rules !"); exit(EXIT_FAILURE);
   return 0;
}

//-------------------------------------------------------
// Get PCB parameters
//-------------------------------------------------------

// Means really within, not at the borders
int Within(int val, int l, int u) {
  return (val > l) && (val < u);
}

int ValidBBox() {
  return (XMin < REAL_MAX) && (XMax > -REAL_MAX) &&
         (YMin < REAL_MAX) && (YMax > -REAL_MAX) &&
         (XMax - XMin > 1000) && (YMax - YMin > 1000); // Could make this much bigger, but that's not crucial (currently 0.1 mm)
}

// Update bounding box with another box
void UpdateBBoxBox(int xmin, int ymin, int xmax, int ymax) {
   XMin = min(XMin, xmin);
   XMax = max(XMax, xmax);
   YMin = min(YMin, ymin);
   YMax = max(YMax, ymax);
}

void UpdateBBoxWire(UL_WIRE W, int layer) {
  if (W.layer == layer) {
     real w2 = W.width/2;
     real xmin = min(W.x1 - w2, W.x2 - w2), ymin = min(W.y1 - w2, W.y2 - w2);
     real xmax = max(W.x1 + w2, W.x2 + w2), ymax = max(W.y1 + w2, W.y2 + w2);
     if (W.arc)
        if (W.arc.angle2 > 360)
           xmax = W.arc.xc + W.arc.radius + w2;
        else if (((W.arc.angle1 <  90) && (W.arc.angle2 >  90)) || (W.arc.angle2 > 450))
           ymax = W.arc.yc + W.arc.radius + w2;
        else if (((W.arc.angle1 < 180) && (W.arc.angle2 > 180)) || (W.arc.angle2 > 540))
           xmin = W.arc.xc - W.arc.radius - w2;
        else if (((W.arc.angle1 < 270) && (W.arc.angle2 > 270)) || (W.arc.angle2 > 630))
           ymin = W.arc.yc - W.arc.radius - w2;
     UpdateBBoxBox(xmin, ymin, xmax, ymax);
  }
}

void UpdateBBoxCircle(UL_CIRCLE C, int layer) {
   if (C.layer == layer) {
      real w2 = C.width/2;
      UpdateBBoxBox(C.x - C.radius - w2, C.y - C.radius - w2, C.x + C.radius + w2, C.y + C.radius + w2);
   }
}

void UpdateBBox(int layer, int el_origin) {
   board(B) {
      B.wires(W) UpdateBBoxWire(W, layer);
      B.circles(C) UpdateBBoxCircle(C, layer);
      B.elements(E) {
         if (el_origin) UpdateBBoxBox(E.x, E.y, E.x, E.y);  // Elements are always on signal layers.
         E.package.wires(W) UpdateBBoxWire(W, layer);
         E.package.circles(C) UpdateBBoxCircle(C, layer);
      }
  }
}

void GetDruParams() {
   string lines[];
   int nrlines = fileread(lines, DruFile);
   if (nrlines == 0) dlgMessageBox("Error reading design rules !");
   for (int i = 0; i < nrlines; ++i) {
      string words[];
      int nrwords = strsplit(words, lines[i], ' ');
      if (nrwords < 3) continue;    // Empty line or some other stuff
      string keyword = words[0];
      if (keyword == "mtCopper") {
         CopperThicknessOutside = Str2U(words[2]);
         MaterialThickness += CopperThicknessOutside;
         if (nrwords != 18) dlgMessageBox("Unexpected design rules !");
         // Check the inner thicknesses:
         for (int j = 3, ct = Str2U(words[j]); j < NrUsedLayers + 1; ct = Str2U(words[++j])) {
            CopperThicknessInside = min(ct, CopperThicknessInside);
            MaterialThickness += ct;
         }
         if (NrUsedLayers >= 2) {
            ct = Str2U(words[17]);
            CopperThicknessOutside = min(ct, CopperThicknessOutside);
            MaterialThickness += ct;
         }
      }
      else if (keyword == "mtIsolate") {
         if (nrwords != 17) dlgMessageBox("Unexpected design rules !");
         // n used layers => n-1 isolate layers. If only 1 layer, also 1 isolate layer.
         for (int k = 2; k < max(3, NrUsedLayers + 1); ++k)
            MaterialThickness += Str2U(words[k]);
      }
      else if (keyword == "mdSmdSmd")
         MinPitch = Str2U(words[2]);
   }
}

void CalcMinTraceWidth() {
   board(B) {
      B.wires(W) if (W.layer <= 16) MinTraceWidth = min(W.width, MinTraceWidth);
      B.signals(S) {
         S.polygons(P) if (P.layer <= 16) MinTraceWidth = min(P.width, MinTraceWidth);
         S.wires(W) if (W.layer <= 16) MinTraceWidth = min(W.width, MinTraceWidth);
      }
   }
}

void CheckHoles() {
   int idx[], start[], end[], k;
   board(B) {
      B.holes(H) MinHoleSize = min(MinHoleSize, H.drill);
      B.signals(S) S.vias(V) {
         MinHoleSize = min(MinHoleSize, V.drill);
         // Collect blind/buried holes !
         if ((V.start > 1) || (V.end < 16)) {
            start[k] = V.start;
            end[k] = V.end;
            ++k;
         }
      }
      B.elements(E) {
         E.package.contacts(C) if (C.pad)
            MinHoleSize = min(MinHoleSize, C.pad.drill);
         E.package.holes(H) MinHoleSize = min(MinHoleSize, H.drill);
      }
   }
   // NrBlindBuriedTypes: Find out how many different ones exist !
   sort(k, idx, start, end);
   for (int l = 0, cur_s = 0, cur_e = 0; l < k; ++l)
      if ((start[idx[l]] != cur_s) || (end[idx[l]] != cur_e)) {
         ++NrBlindBuriedTypes;
         cur_s = start[idx[l]];
         cur_e = end[idx[l]];
      }
}

void GetPCBParams() {
   // Check out layers:
   int smask_top, smask_bottom, silk_top, silk_bottom, finish;
   board(B) {
      BoardName = filename(B.name);
      B.layers(L) if (L.used)
         if (L.number <= 16) ++NrUsedLayers;
         else if (L.number == LAYER_TSTOP) smask_top = 1;
         else if (L.number == LAYER_BSTOP) smask_bottom = 1;
         else if (L.number == LAYER_TPLACE) silk_top = 1;    // Could also take TNAMES/TVALUES. Leave the criterium less strict
         else if (L.number == LAYER_BPLACE) silk_bottom = 1; // Could also take BNAMES/BVALUES. Leave the criterium less strict
   }
   SolderSides = smask_top ? (smask_bottom ? "Both Sides" : "Top Side") :
                             (smask_bottom ? "Bottom Side" : "None");
   SilkScreenSides = (silk_top) ? (silk_bottom ? "Both Sides" : "Top Side") :
                                  (silk_bottom ? "Bottom Side" : "None");
   if (NrUsedLayers == 0) {
      Warnings += LItem(tr("None of the signal layers are used. Number of layers could not be determined."));
      Useless = 1;
   }

   // Board outlines:
   UpdateBBox(LAYER_DIMENSION, 0);
   if (!ValidBBox()) {
      Warnings += "<li>" + tr("Board width and length could not be determined from dimension layer. ");
      UpdateBBox(LAYER_TOP, 1);
      UpdateBBox(LAYER_BOTTOM, 1);
      if (!ValidBBox())
         Warnings += tr("Estimate based on outer layers failed. ") +
                     tr("Please use the dimension layer to design the board outline.") + "</li>";
      else
         Warnings += tr("Estimation based on outer layers. ") + "</li>";
   }

   CalcMinTraceWidth();
   if (MinTraceWidth == INT_MAX)
      Warnings += LItem(tr("No copper found in the signal layers. ") +
                        tr("Minimum trace width could not be determined."));
   if (MinTraceWidth == 0)
      Warnings += LItem(tr("Wire(s) and/or polygon(s) with zero width found on signal layer(s). ") +
                        tr("Minimum trace width could not be determined."));
   GetDruParams();
   CheckHoles();
   int air_wires = 0;
   {  // Check if there are still airwires:
      board(B) {
         B.wires(W) if (W.layer == LAYER_UNROUTED) air_wires = 1;
         B.signals(S) {
            S.polygons(P) if (P.layer == LAYER_UNROUTED) air_wires = 1;
            S.wires(W) if (W.layer == LAYER_UNROUTED) air_wires = 1;
         }
      }
   }
   if (air_wires)
      Warnings += LItem(tr("There are still airwires left."));

   // Count SMD pads
   board(B) B.elements(E) E.package.contacts(C)
      if (C.smd)
         if (C.smd.layer == LAYER_TOP) ++NrSmdPadsTop;
         else ++NrSmdPadsBottom;
}

string MakeParamSendString() {
   // Parameters that always can be determined:
   string send = "?source=eagle";
   if (Target == Element14)
      send +=    "&PCBSource=USQuickTurn";
   if (Target == EuroCircuits)
      send +=    "&boardName=" + BoardName;
   send +=       "&numLayers=" + I2Str(NrUsedLayers) +
                 "&materialThickness=" + U2EUStr(MaterialThickness) +
                 "&copperThicknessOutside=" + U2CoppThickEUStr(CopperThicknessOutside) +
                 "&solderSides=" + SolderSides +
                 "&silkScreenSides=" + SilkScreenSides +
                 "&blindBuriedHoles=" + I2Str(NrBlindBuriedTypes) +
                 "&numPadsTop=" + I2Str(NrSmdPadsTop) +
                 "&numPadsBottom=" + I2Str(NrSmdPadsBottom);
   // Parameters that might miss:
   if (ValidBBox())
      send +=    "&boardWidth=" + U2EUStr(XMax - XMin) +
                 "&boardLength=" + U2EUStr(YMax - YMin);
   if (Within(CopperThicknessInside, 0, INT_MAX))
      send +=    "&copperThicknessInside=" + U2CoppThickEUStr(CopperThicknessInside);
   if (Within(MinTraceWidth, 0, INT_MAX))
      send +=    "&minTraceWidth=" + U2EUStr(MinTraceWidth);
   if (MinPitch < INT_MAX)
      send +=    "&minPitch=" + U2EUStr(MinPitch);
   if (MinHoleSize < INT_MAX)
      send +=    "&minHoleSize=" + U2EUStr(MinHoleSize);

   if (Debug) output(DbgFile, "wba") printf("%s\n%s\n", GetTargetURL(), send);
   return send;
}

int Dialog() {
   // Info/help, depending on language and target...
   string Info[] = {
   "Based on your board layout and the design rules, key parameters for manufacturing "
   "your board like board size, minimum hole size etc. are determined. Your design "
   "should be complete and have passed a DRC successfully.<br>"
   "By following the link appearing below you get to the quote site of one of our partners "
   "(country dependent) where these parameters are transferred. With a few steps you get a "
   "quote for manufacturing your board this way."
   "<p>" +
   (Target == Element14 ?
      "For North America there's also an assembly service available through our partner <i>Screaming Circuits</i>."
   :  "Additionally, from our partner <b>Eurocircuits</b> design rules are available, which are adjusted "
      "to their services and standards. See  "
      "<a href=\"http://www.eurocircuits.com/index.php/eagle-dru-files\">DRU files Eurocircuits<a>.")
   ,
   "Basierend auf Ihr Board-Layout und den Designregeln werden wichtige Parameter zur Fertigung "
   "des Boards ermittelt wie zum Beispiel Boardgrösse, kleinster Bohrdurchmesser usw. <br>"
   "Ihr Design sollte möglichst vollständig und ein erfolgreicher DRC durchgeführt worden sein.<br>"
   "Durch Klicken des unten erscheinenden Links gelangen Sie zur Angebotsseite einer unserer Partner "
   "(landesabhängig), wo diese Parameter übernommen werden. Mit wenigen Schritten erhalten Sie so "
   "ein Angebot zur Fertigung Ihres Boards."
   "<p>" +
   (Target == Element14 ?
      "Für Nordamerika ist durch unseren Partner <i>Screaming Circuits</i> auch ein Assembly-Service verfügbar."
   :  "Zusätzlich sind von unserem Partner <b>Eurocircuits</b> Designregeln verfügbar, die auf deren "
      "Services und Standards abgestimmt sind. Siehe  "
      "<a href=\"http://www.eurocircuits.com/index.php/eagle-dru-files\">DRU-Dateien Eurocircuits</a>.")
   };
   string url = "<a href=\"" + GetTargetURL() + MakeParamSendString() + "\">";
   string invisLabel = "<b>" + url + "</b>";
   string visLabel = "<b>" + url + tr("Get PCB Quote") + "</b>";
   string label = (Target == Element14) ? visLabel : invisLabel;
   return dlgDialog(tr("PCB Quote Service")) {
      dlgHBoxLayout dlgSpacing(470);
      dlgGroup(tr("Information:"))
          dlgLabel(Info[LangIdx], 1);
      if (Warnings)
         dlgHBoxLayout
            dlgGroup(tr("Warnings:"))
               dlgLabel(Warnings);
      if (!Useless) {
         dlgGroup(tr("Parameters:"))
            dlgGridLayout {
               int Row;
               dlgCell(Row, 0) dlgLabel(tr("Number of layers:"));                       dlgCell(Row++, 1) dlgLabel(Bold(I2Str(NrUsedLayers)));
               dlgCell(Row, 0) dlgLabel(tr("Board name:"));                             dlgCell(Row++, 1) dlgLabel(Bold(BoardName));
               dlgCell(Row, 0) dlgLabel(tr("Board width  (dimension X):"));             dlgCell(Row++, 1) dlgLabel(Bold(ValidBBox() ? U2EUStrN(XMax - XMin) : Unknown));
               dlgCell(Row, 0) dlgLabel(tr("Board length (dimension Y):"));             dlgCell(Row++, 1) dlgLabel(Bold(ValidBBox() ? U2EUStrN(YMax - YMin) : Unknown));
               dlgCell(Row, 0) dlgLabel(tr("Board thickness:"));                        dlgCell(Row++, 1) dlgLabel(Bold(U2EUStrN(MaterialThickness)));
               dlgCell(Row, 0) dlgLabel(tr("Copper thickness outer layers:"));          dlgCell(Row++, 1) dlgLabel(Bold(U2CoppThickEUStrN(CopperThicknessOutside)));
               dlgCell(Row, 0) dlgLabel(tr("Copper thickness inner layers:"));          dlgCell(Row++, 1) dlgLabel(Bold(Within(CopperThicknessInside, 0, INT_MAX) ? U2CoppThickEUStrN(CopperThicknessInside) : Unknown));
               dlgCell(Row, 0) dlgLabel(tr("Solder sides:"));                           dlgCell(Row++, 1) dlgLabel(Bold(tr(SolderSides)));
               dlgCell(Row, 0) dlgLabel(tr("Silkscreen sides:"));                       dlgCell(Row++, 1) dlgLabel(Bold(tr(SilkScreenSides)));
               dlgCell(Row, 0) dlgLabel(tr("Number of SMD pads on top:"));              dlgCell(Row++, 1) dlgLabel(Bold(I2Str(NrSmdPadsTop)));
               dlgCell(Row, 0) dlgLabel(tr("Number of SMD pads on bottom:"));           dlgCell(Row++, 1) dlgLabel(Bold(I2Str(NrSmdPadsBottom)));
               dlgCell(Row, 0) dlgLabel(tr("Number of blind or buried hole types:"));   dlgCell(Row++, 1) dlgLabel(Bold(I2Str(NrBlindBuriedTypes)));
               dlgCell(Row, 0) dlgLabel(tr("Minimum trace width (track width):"));      dlgCell(Row++, 1) dlgLabel(Bold(Within(MinTraceWidth, 0, INT_MAX) ? U2EUStrN(MinTraceWidth) : Unknown));
               dlgCell(Row, 0) dlgLabel(tr("Minimum SMD pitch:"));                      dlgCell(Row++, 1) dlgLabel(Bold(MinPitch < INT_MAX ? U2EUStrN(MinPitch) : Unknown));
               dlgCell(Row, 0) dlgLabel(tr("Minimum hole size:"));                      dlgCell(Row++, 1) dlgLabel(Bold(MinHoleSize < INT_MAX ? U2EUStrN(MinHoleSize) : Unknown));
            }
         dlgHBoxLayout {
            dlgLabel(tr("Change Country:"));
            dlgComboBox(Countries, CountryIdx) {
               InitCountry();
               dlgAccept(1); // Display again with different country / target
            }
            dlgStretch(1);
         }
      }
      dlgHBoxLayout {
         if (Target != Element14 && !Useless)
            dlgPushButton(tr("+Continue...")) {
               label = visLabel; // Make link visible
               NotifyE14();
            }
         dlgStretch(1);
         dlgLabel(label, 1);
         dlgStretch(1);
         dlgPushButton(tr("Close")) dlgReject();
      }
   };
}

//-----------------------------------------------------------------------------
// main section
//-----------------------------------------------------------------------------

// Parse arguments
for (int i = 1; i <= argc; ++i) {
   if (argv[i] == "-noexp") Export = 0;
}

if (board) {
   string dir = filedir(argv[0]);
   board(B) DruFile = dir + "dl-" + filename(filesetext(B.name, ".dru"));
   if (Export)
      exit("DRC SAVE '" + DruFile + "';\nRUN '" + argv[0] + "' -noexp;");
   if (Debug) board(B) {
     DbgFile = filedir(B.name) + "/dbg-pcb.txt";
     output(DbgFile, "wba") printf("\nBoard: %s\n", filename(B.name));
   }
   InitCountry();
   status(tr("Calculating quote parameters..."));
   GetPCBParams();
   if (Warnings) {
      string tmp = tr("Your board layout is incomplete:") + "<ul>" + Warnings + "</ul>";
      if (Useless) tmp += tr("A quote for this board doesn't make sense yet !");
      else tmp += tr("If you want to get a quote anyway, please follow the link.");
      Warnings = tmp;
   }
   if (Debug && Warnings) output(DbgFile, "wba") printf("Warnings: \n%s\n", Warnings);
   while (Dialog() == 1);
   exit(EXIT_SUCCESS);
}
else
   dlgMessageBox(tr("Please start from Layout editor !"));
